# REQ TII70 L2

# Specification: Requirements Document
- ReqIF.Description: Requirements Document

## 1: Adaptación de la Base
Trace
El Centro de Lanzamiento Punta Indio (CLPI) deberá tener la capacidad de adecuar sus instalaciones a todas las misiones suborbitales TII-70 del programa ISCUL.
- LongName: L1-MIS-001
  L0-PRO-003
- ChapterName: L2
- ReqStatus: Asignado
- ReqType: operacional
- VerifiedBy: Revisión

## 5: Seguridad de Polígono
El servicio de Seguridad de PolÃ­gono del centro de lanzamiento adoptará las directivas y polÃ­ticas de seguridad establecidas por la CONAE y adoptadas por el programa ISCUL.
- LongName: L0-PRO-005
  L1-MIS-009
- ChapterName: L2
- ReqStatus: Asignado
- ReqType: operacional
- VerifiedBy: Revisión

## 6: Autoridad de Seguridad
La infraestrutura terrena deberá responder con todas las actividades operativas y entidades que la autoridad de seguridad de polígono requiera.
- LongName: L0-PRO-005
  L1-MIS-009
- ChapterName: L2
- ReqStatus: Asignado
- ReqType: operacional
- VerifiedBy: Revisión

## 8: Tiempo de Suspención
El tiempo de suspensión de actividades de Lanzamiento Nominal no puede superar los 6 meses.
- LongName: L1-MIS-017
- ChapterName: L2
- ReqStatus: No Asignado
- ReqType: diseño
- VerifiedBy: Análisis

## 9: Centro de Control
"La base de lanzamiento deberá estar diseñada para que todas las operaciones en los escenarios de: Lanzamiento Nominal, Ensayos, Recuperación, Contingencias, puedan ser realizadas desde el Centro de Control de Lanzamiento."
- LongName: L0-PRO-005
- ChapterName: L2
- ReqStatus: No Asignado
- ReqType: diseño
- VerifiedBy: Revisión

## 10: Multimisión con Recuperación
Las operaciones de lanzamiento desde Punta Indio (CLPI) deberá desarrollar todas sus procesos compatibles con misiones suborbitales con recuperación
- LongName: L1-MIS-008
- ChapterName: L2
- ReqStatus: Asignado
- ReqType: operacional
- VerifiedBy: Revisión

## 11: Actualización
La infraestructura terrena deberá admitir actualizaciones de equipos y tecnologí­a sin interrumpir su capacidad de operación.
- ChapterName: L2
- ReqStatus: No Asignado
- ReqType: operacional
- VerifiedBy: Revisión

## 13: Hangar
Se deberá implementar un Hangar de Campaña con las condiciones ambientales necesarias para el procesamiento e integración de las cargas útiles en el TII-70.
- LongName: L2-SIS-014
- ChapterName: L2
- ReqStatus: Asignado
- ReqType: configuración
- VerifiedBy: Revisión

## 14: Atención de Carga Útil
Las instalaciones del Centro de Lanzamiento Punta Indio deberán proveer un sistema dedicado a la atención de la carga útil en todo el ciclo de vida desde el arribo a la base.
- LongName: L1-MIS-002
- ChapterName: L2
- ReqStatus: Asignado
- ReqType: configuración
- VerifiedBy: Revisión

## 15: Umbilicales
Las instalaciones del Centro de Lanzamiento Punta Indio deberán proveer un sistema de umbilicales dedicado a la atención del Vehí­culo Lanzador a partir de su integración al soporte de lanzamiento.
- ChapterName: L2
- ReqStatus: Asignado
- ReqType: configuración
- VerifiedBy: Revisión

## 16: Hardware de Seguridad
El servicio de Seguridad del Polígono del Centro de Lanzamiento Punta Indio deberá implementar hardware y software de Tierra necesario para dar soporte a la Seguridad de Vuelo.
- LongName: L1-MIS-009
- ChapterName: L2
- ReqStatus: Asignado
- ReqType: funcional
- VerifiedBy: Revisión

## 18: Tiempo Operativo
La base de lanzamiento deberá tener la capacidad de dar soporte de preparación y lanzamiento del vehículo lanzador durante 10 días corridos (TBC).
- LongName: L1-MIS-017
- ChapterName: L2
- ReqStatus: No Asignado
- ReqType: operacional
- VerifiedBy: Análisis

## 19: Tiempo de Preparación
El período de preparación para un lanzamiento solicitado no podrá extenderse por más de 80 dí­as corridos desde el comienzo formal de las operaciones.
- LongName: L1-MIS-017
- ChapterName: L2
- ReqStatus: No Asignado
- ReqType: diseño
- VerifiedBy: Análisis

## 20: Durabilidad
El diseño de la base de lanzamiento deberá contemplar un plan de mantenimiento de los elementos sujetos a desgaste operativo o climático para una vida útil mínima de la base de lanzamiento de 10 años.
- LongName: L0-PRO-003
- ChapterName: L2
- ReqStatus: No Asignado
- ReqType: diseño
- VerifiedBy: Revisión

## 21: Telemetria y Telecomando
El sistema TII-70 utilizará estaciones de telemetrí­a y telecomando que aseguren el radio enlace durante toda la misión
- LongName: L0-PRO-001
  L0-PRO-002
- ChapterName: L2
- ReqStatus: Asignado
- ReqType: configuración
- VerifiedBy: Análisis

## 22: Manual de Usuario
"La ingfraestructura de tierra, como entidad operativa, deberá disponer un manual de usuario."
- ChapterName: L2
- ReqStatus: No Asignado
- ReqType: operacional
- VerifiedBy: Inspección

## 23: Suministro de Fluidos
"La base de lanzamiento Punta Indio deberá contar un un servicio de suministro de LOx, Kerosene, He, N2, aire acondicionado, potencia electrica, potencia hidráulica y agua de refrigeración para los ensayos estáticos y lanzamientos"
- ChapterName: L2
- ReqStatus: Asignado
- ReqType: funcional
- VerifiedBy: Revisión

## 24: Dimensión del Vehículo
El diámetro del vehículo será de 70cm (TBC).
- ChapterName: L2
- ReqStatus: No Asignado
- ReqType: MOP
- VerifiedBy: Inspección

## 25: Aceleración Axial Máxima
La aceleración axial cuasi-estítica específica debe ser igual o menor a 9g (TBC) en todo el vuelo.
- ChapterName: L2
- ReqStatus: No Asignado
- ReqType: MOP
- VerifiedBy: Análisis

## 27: FTS
"Debe incluirse un Sistema de terminación de vuelo (STV ó FTS) con posibilidad de accionamiento automática o por comando, mientras el vuelo pueda alcanzar zonas protegidas."
- LongName: L1-MIS-009
- ChapterName: L2
- ReqStatus: Asignado
- ReqType: configuración
- VerifiedBy: Revisión

## 26: Aceleración Axial Nominal
"La aceleración axial cuasi-estática específica de lanzamiento será mayor o igual a 1,3g. (TBC)"
- ChapterName: L2
- ReqStatus: No Asignado
- ReqType: MOP
- VerifiedBy: Análisis

## 28: HMS
"El vehículo debe contar con un sistema automático que releve las variables más importantes para enviar al segmento de Soporte en Tierra, para la habilitación del lanzamiento."
- LongName: L1-MIS-022
- ChapterName: L2
- ReqStatus: Asignado
- ReqType: funcional
- VerifiedBy: Revisión

## 29: Presión Dinámica
La configuración deberá soportar una presión dinámica de hasta 40kPa (TBC) en la fase de ascenso.
- ChapterName: L2
- ReqStatus: No Asignado
- ReqType: MOP
- VerifiedBy: Análisis

## 30: Flotabilidad
"La configuración deberá tener un sistema que, luego del impacto, permita que el vehí­culo flote íntegramente y cuente con puntos de sujeción para su remoción del agua."
- LongName: L1-MIS-008
- ChapterName: L2
- ReqStatus: Asignado
- ReqType: configuración
- VerifiedBy: Revisión

## 31: Propulsor TRAF
Las especificaciones técnicas del propulsor son las impuestas por el programa TRAF
- LongName: L0-PRO-001
- ChapterName: L2
- ReqStatus: No Asignado
- ReqType: diseño
- VerifiedBy: Revisión

## 32: Interrupción del Lanzamiento
Las operaciones de lanzamiento deberán incluir una interrupción autónoma si existiera cualquier condición no tolerada.
- LongName: L1-MIS-022
- ChapterName: L2
- ReqStatus: Asignado
- ReqType: diseño
- VerifiedBy: Revisión

## 33: Redundancia
"Deberá realizarse un análisis de confiabilidad del sistema que permita determinar los componentes a ser redundados, contemplando por otro lado, el costo en peso asociado, el impacto en la misión y en la operación segura."
- LongName: L1-MIS-022
- ChapterName: L2
- ReqStatus: No Asignado
- ReqType: garantía de producto
- VerifiedBy: Análisis

## 34: Interrupción del los Procesos
"Las operaciones de lanzamiento deberán incluir la posibilidad de supervisión e intervención en cualquier momento del proceso, a partir de cual el operador puede ejecutar las operaciones de recuperación en forma segura."
- ChapterName: L2
- ReqStatus: Asignado
- ReqType: operacional
- VerifiedBy: Revisión

## 35: Tipo de Lanzamiento
El vehículo deberá ser lanzado en forma vertical.
- LongName: L1-MIS-025
- ChapterName: L2
- ReqStatus: Asignado
- ReqType: físico
- VerifiedBy: Revisión

## 36: Trayectoria
La trayectoria de ascenso tendrá un tramo vertical hasta liberar la altitud de infraestructuras cercana.
- LongName: L1-MIS-025
  L1-MIS-010
- ChapterName: L2
- ReqStatus: No Asignado
- ReqType: ambiente
- VerifiedBy: Revisión

## 37: Giro Gravitatorio
La trayectoria de ascenso nominal propulsado será de un giro gravitatorio.
- LongName: L1-MIS-025
  L1-MIS-010
- ChapterName: L2
- ReqStatus: No Asignado
- ReqType: operacional
- VerifiedBy: Revisión

## 38: TVC
El control de actitud deberá utilizar como actuador la vectorización del empuje del motor principal durante su quema.
- LongName: L1-MIS-025
  L1-MIS-010
- ChapterName: L2
- ReqStatus: Asignado
- ReqType: funcional
- VerifiedBy: Revisión

## 39: RCS
El control de actitud deberá utilizar como actuador el sistema de control por reacción luego de la quema del motor principal.
- LongName: L1-MIS-025
  L1-MIS-010
- ChapterName: L2
- ReqStatus: Asignado
- ReqType: funcional
- VerifiedBy: Revisión

## 40: Alineación del Propulsor
El motor principal deberá tener un método para alinearse en forma automática antes del lanzamiento.
- ChapterName: L2
- ReqStatus: Asignado
- ReqType: diseño
- VerifiedBy: Revisión

## 41: Cinemática de Rotación
El sistema deberá controlar la cinemática de rotación de vuelo al inicio de la reentrada.
- ChapterName: L2
- ReqStatus: Asignado
- ReqType: funcional
- VerifiedBy: Revisión

## 43: Guiado de Acimut
El sistema deberá implementar un guiado de acimut.
- LongName: L1-MIS-025
  L1-MIS-010
- ChapterName: L2
- ReqStatus: Asignado
- ReqType: funcional
- VerifiedBy: Revisión

## 44: Guiado de Altitud
El sistema deberá implementar un guiado de altitud.
- LongName: L1-MIS-025
  L1-MIS-010
- ChapterName: L2
- ReqStatus: Asignado
- ReqType: funcional
- VerifiedBy: Revisión

## 45: Condición de Terminación
El sistema deberá evaluar abordo la condición de terminación.
- LongName: L1-MIS-009
- ChapterName: L2
- ReqStatus: Asignado
- ReqType: funcional
- VerifiedBy: Revisión

## 46: NGCT
El sistema deberá reportar los resultados de cada algoritmo de NGCT y sus variables de entrada hacia la computadora de telemetría.
- LongName: L1-MIS-009
- ChapterName: L2
- ReqStatus: Asignado
- ReqType: funcional
- VerifiedBy: Revisión

## 47: Interfaces de NGCT
"Las funciones de NGCT deben contar con una interfaz con las de Propulsión, Recuperación y la Carga Útil, para la implementación de los eventos nominales de misión."
- LongName: L1-MIS-010
- ChapterName: L2
- ReqStatus: Asignado
- ReqType: funcional
- VerifiedBy: Revisión

## 57: Cofia
El perfil de la cofia deberá tener un concepto útil para la evaluación de las condiciones del TII-250.
- LongName: L0-PRO-001
  L0-PRO-002
- ChapterName: L2
- ReqStatus: No Asignado
- ReqType: físico
- VerifiedBy: Revisión

## 58: Comunicación de Carga Útil
El sistema deberá proveer interfaces de comunicaciones para las cargas útiles.
- LongName: L1-MIS-002
- ChapterName: L2
- ReqStatus: Asignado
- ReqType: interface
- VerifiedBy: Revisión

## 60: Posicionamiento Global
El sistema deberá contar con la capacidad de determinar la posición el vehí­culo una vez culminado el vuelo.
- LongName: L1-MIS-010
- ChapterName: L2
- ReqStatus: Asignado
- ReqType: funcional
- VerifiedBy: Revisión

## 63: Tiempo de Quema
El tiempo de quema en vuelo deberá ser de al menos 2 minutos (TBD).
- LongName: L1-MIS-014
- ChapterName: L2
- ReqStatus: No Asignado
- ReqType: MOP
- VerifiedBy: Análisis

## 65: Energía Eléctrica
El segmento de tierrra deberá proveer de energia eléctrica al segmento de vuelo
- ChapterName: L2
- ReqStatus: Asignado
- ReqType: funcional
- VerifiedBy: Revisión

## 68: Radio Enlace
"El sistema deberá implementar la capacidad de comunicación mediante radio enlace en banda S, implementando un canal para datos críticos y un canal general para datos de telemetría."
- ChapterName: L2
- ReqStatus: Asignado
- ReqType: funcional
- VerifiedBy: Revisión

## 69: Video en Tiempo Real
El sistema deberá tener la capacidad de transmitir el video en tiempo real de todos los eventos del lanzamiento.
- ChapterName: L2
- ReqStatus: Asignado
- ReqType: funcional
- VerifiedBy: Revisión

## 74: Servicio de Telemetría
El sistema deberá tener la capacidad de generar servicio de telemetría a la carga util.
- LongName: L1-MIS-002
- ChapterName: L2
- ReqStatus: Asignado
- ReqType: funcional
- VerifiedBy: Revisión

## 75: Banda S
La bajada de video se harÃ¡ por banda S.
- ChapterName: L2
- ReqStatus: Asignado
- ReqType: interface
- VerifiedBy: Revisión

## 76: Compatibilidad Electromagnética
El sistema deberá aplicar la MIL-STD-461 para garantizar que las emisiones radiadas o conducidas de todos los equipos electrónicos de abordo no interfieran afectando su normal funcionamiento.
- LongName: L1-MIS-022
  L0-PRO-005
- ChapterName: L2
- ReqStatus: No Asignado
- ReqType: Restricción
- VerifiedBy: Revisión

## 77: Almacenamiento y Transporte
Los sistemas de almacenamiento y transporte del vehículo deberán diseñarse para asegurar la integridad del mismo con el registro de variables ambientales.
- ChapterName: L2
- ReqStatus: Asignado
- ReqType: diseño
- VerifiedBy: Revisión

## 78: Hangar de Almacenaje
El sitio de almacenaje y operaciones finales sobre el segmento de vuelo en Capetina deberá realizarse en un Hangar de Campaña a ser construido.
- ChapterName: L2
- ReqStatus: Asignado
- ReqType: operacional
- VerifiedBy: Inspección

## 79: Utilajes
El Hangar de Campaña (Capetina) deberá tener un sistema que permita extraer el cohete de su contenedor de transporte.
- ChapterName: L2
- ReqStatus: Asignado
- ReqType: operacional
- VerifiedBy: Inspección

## 80: Determinación de Propiedades
El Hangar de Campaña (Capetina) deberá contener un sistema para determinar las propiedades de masa finales del vehículo.
- ChapterName: L2
- ReqStatus: Asignado
- ReqType: operacional
- VerifiedBy: Inspección

## 81: Montajes
El Hangar de Campaña (Capetina) deberá tener un sistema que permita instalar el cohete en el sistema de verticalización.
- ChapterName: L2
- ReqStatus: Asignado
- ReqType: operacional
- VerifiedBy: Inspección

## 82: Integración
"El Hangar de Campaña (Capetina) deberá tener vias de integración donde se pueda disponer el cohete de modo que permita realizar tareas de integración de: a) La carga útil, instalar en el módulo de carga útil y en la cofia b) Realizar re-trabajos sobre el resto de los módulos, c) Instalar paracaí­das. d) Instalar aletas."
- ChapterName: L2
- ReqStatus: Asignado
- ReqType: operacional
- VerifiedBy: Inspección

## 83: Retención
El vehí­culo estará retenido hasta que se verifíque un conjunto de condiciones necesarias para liberarlo con bajo riesgo.
- LongName: L0-PRO-005
- ChapterName: L2
- ReqStatus: Asignado
- ReqType: funcional
- VerifiedBy: Revisión

## 84: Torre
El vehículo será transportado desde el hangar hasta el sitio de lanzamiento con un sistema que permita verticalizarlo una vez acoplado al PAD (plataforma de lanzamiento).
- ChapterName: L2
- ReqStatus: Asignado
- ReqType: operacional
- VerifiedBy: Revisión

## 85: Alineación del VL
El vehÃ­culo deberÃ¡ poder ser alineado en su verticalidad.
- ChapterName: L2
- ReqStatus: Asignado
- ReqType: físico
- VerifiedBy: Inspección

## 86: Referencias
El eje axial del motor deberá poder ser medido en relación con los apoyos del PAD.
- ChapterName: L2
- ReqStatus: Asignado
- ReqType: interface
- VerifiedBy: Ensayo

## 87: Carga de Propelentes
Los propelentes deberán ser cargados y descargados de manera remota a travez del banco de carga de propelentes (BCP) en condiciones nominales y ante contingencias.
- ChapterName: L2
- ReqStatus: Asignado
- ReqType: operacional
- VerifiedBy: Revisión

## 88: Conectores Umbilicales
Los umbilicales eláctricos deberán tener conectores de desconexión automática al momento del despegue.
- ChapterName: L2
- ReqStatus: Asignado
- ReqType: configuración
- VerifiedBy: Revisión

## 89: Ensayo de Fuego
Un modelo del vehículo será encendido en PAD por un tiempo de quema que permita evaluar las condiciones nominales.
- LongName: L1-MIS-022
- ChapterName: L2
- ReqStatus: Asignado
- ReqType: verificación
- VerifiedBy: Revisión

## 90: Ensayo de Carga
"Cada vehículo de vuelo deberá ser ensayado con carga/descarga de líquidos y gases en el PAD, con presurización de tanques principales."
- ChapterName: L2
- ReqStatus: Asignado
- ReqType: verificación
- VerifiedBy: Ensayo

## 91: Alineación TVC
Cada vehÃ­culo de vuelo deberá poder ensayar el método de alineación del TVC del propulsor con tuberías presurizadas.
- ChapterName: L2
- ReqStatus: Asignado
- ReqType: verificación
- VerifiedBy: Ensayo

## 92: Centro de Control
"Ingeniería de Operaciones deberá desarrollar el centro de operaciones de lanzamiento, la documentación, la formacion de los rrhh y el aseguramiento de las operaciones para al menos los escenarios alistamiento, vuelo, post vuelo y contingencia."
- ChapterName: L2
- ReqStatus: Asignado
- ReqType: operacional
- VerifiedBy: Revisión

## 93: Concepto de Operación
Ingeniería de Operaciones deberá generar el concepto de operación de la misión TII-70.
- ChapterName: L2
- ReqStatus: No Asignado
- ReqType: operacional
- VerifiedBy: Revisión

## 94: Gestión de Comandos y Datos
"El centro de operaciones de lanzamiento deberá generar comandos y recolectar la telemetría, centralizando, estandarizando y vizualizando toda la información de los diferentes elementos que intervienen en las distintas etapas de la misión."
- ChapterName: L2
- ReqStatus: Asignado
- ReqType: diseño
- VerifiedBy: Revisión

## 95: Referencia de Tiempo
El centro de operaciones de lanzamiento deberÃ¡ generar una referencia de tiempo Ãºnica para todas los sistemas que intervienen en las etapas del lanzamiento.
- ChapterName: L2
- ReqStatus: Asignado
- ReqType: diseño
- VerifiedBy: Revisión

## 96: Comunicaciones Generales
El centro de operaciones de lanzamiento deberÃ¡ centralizar y gestionar las comunicaciones y videos en las etapas de lanzamiento.
- ChapterName: L2
- ReqStatus: Asignado
- ReqType: diseño
- VerifiedBy: Inspección

## 97: Protección de la Información
El centro de operaciones de lanzamiento deberÃ¡ resguardar y preservar toda la informaciÃ³n que se genere en la etapa de lanzamiento y posterior disponibilidad de la misma hacia el Ã¡rea de aseguramiento de misiÃ³n.
- ChapterName: L2
- ReqStatus: Asignado
- ReqType: diseño
- VerifiedBy: Revisión

## 48: Sistemas de FTS
"Los Sistemas de seguridad y terminación del vuelo deben derivarse del â€œFlight Termination Systems Commonality Standard 319-10 [D.R.10] para vehículos no tripulados de múltiples etapas, cuando sea aplicable. Los reportes asociados del RCC (Range Commanders Council) y el Eastern and western range (EWR) safety policies and processes EWR-127 [D.R.11] debe considerarse como referencia."
- LongName: L1-MIS-009
- ChapterName: L2
- ReqStatus: Asignado
- ReqType: Restricción
- VerifiedBy: Revisión

## 51: Terminación por Comando
Un Sistema de Terminación por Comando debe permitir al oficial de seguridad de lanzamiento cortar el empuje antes de cualquier acción destructiva sobre el vehículo.
- LongName: L0-PRO-005
- ChapterName: L2
- ReqStatus: Asignado
- ReqType: funcional
- VerifiedBy: Revisión

## 61: Punto de Impacto
El sistema deberá tener la capacidad de calcular el punto de impacto a lo largo de toda la trayactoria
- ChapterName: L2
- ReqStatus: Asignado
- ReqType: funcional
- VerifiedBy: Análisis

## 98: Simulador de Carga Útil
Trace
El dueño de la carga útil deberá proveer un simulador de carga útil para ensayar las interfases en el CPT.
- LongName: L1-MIS-016
- ChapterName: L2
- ReqStatus: Asignado
- ReqType: operacional
- VerifiedBy: Revisión

## 99: Carretón
DeriveReqt
El sistema se interés deberá montarse sobre un carretón estándar.
- LongName: L1-MIS-001
- ChapterName: L2
- ReqStatus: Asignado
- ReqType: soporte logístico
- VerifiedBy: Revisión

## 100: GSE
Trace
DeriveReqt
El sistema de interés deberá contar con su GSE (equipo de soporte de tierra) con la capacidad de llevar adelante los ensayos de rendimiento (CPT)
- LongName: L1-MIS-016
  L1-MIS-022
- ChapterName: L2
- ReqStatus: Asignado
- ReqType: operacional
- VerifiedBy: Revisión

## 101: Sala Limpia
DeriveReqt
El hangar deberá contar con una sala limpia para el almacenaje del SOI clase TBD
- LongName: L1-MIS-022
- ChapterName: L2
- ReqStatus: Asignado
- ReqType: operacional
- VerifiedBy: Revisión

## 102: Transporte LV
El sistema de interés deberá contar con un sistema de transporte apto para el camino existente entre Pipinas y la base de lanzamiento
- LongName: L1-MIS-001
- ChapterName: L2
- ReqStatus: Asignado
- ReqType: operacional
- VerifiedBy: Revisión

## 103: Salud de Transporte
El sistema de interés deberá contar con la instrumentación necesaria para evaluar la salud del sistema durante el transporte del SOI
- LongName: L1-MIS-001
- ChapterName: L2
- ReqStatus: Asignado
- ReqType: diseño
- VerifiedBy: Revisión

## 104: CPT
Los ensayos de CPT (Comprehensive Performance Test) a realizarse sobre el SOI, deberán realizarse desde los umbilicales.
- ChapterName: L2
- ReqStatus: Asignado
- ReqType: verificación
- VerifiedBy: Revisión

## 105: VÃ­as de Integración CU
El Hangar de Campaña (Capetina) deberá tener vías de integración donde se pueda disponer el cohete de modo que permita realizar tareas de integración de la carga útil.
- ChapterName: L2
- ReqStatus: Asignado
- ReqType: operacional
- VerifiedBy: Revisión

## 106: Vías de Integración LV
El Hangar de Campaña (Capetina) deberá tener ví­as de integración donde se pueda disponer el cohete de modo que permita realizar tareas de integración del sistema de interés
- ChapterName: L2
- ReqStatus: Asignado
- ReqType: operacional
- VerifiedBy: Revisión

## 107: Transporte al PAD
La base de lanzamiento deberá contar con facilidades que permitan la manipulación y el transporte del SOI al PAD
- ChapterName: L2
- ReqStatus: Asignado
- ReqType: soporte logístico
- VerifiedBy: Revisión

## 108: Interfaz LOX
DeriveReqt
El SOI deberá contar con una interfaz de oxígeno liquido
- LongName: L1-MIS-014
- ChapterName: L2
- ReqStatus: Asignado
- ReqType: interface
- VerifiedBy: Revisión

## 109: Reservorio Combustible
DeriveReqt
El SOI deberá contar con la capacidad de almacenar la masa de combustible requerida por el propulsor.
- LongName: L1-MIS-014
- ChapterName: L2
- ReqStatus: Asignado
- ReqType: funcional
- VerifiedBy: Revisión

## 110: Reservorio Oxidante
DeriveReqt
El SOI deberá contar con la capacidad de almacenar la masa de oxidante requerida por el propulsor
- LongName: L1-MIS-014
- ChapterName: L2
- ReqStatus: Asignado
- ReqType: funcional
- VerifiedBy: Revisión

## 111: Reservorio N2
DeriveReqt
El SOI deberá contar con la capacidad de almacenar la masa de nitrógeno requerido por el propulsor y el RCS
- LongName: L1-MIS-014
- ChapterName: L2
- ReqStatus: Asignado
- ReqType: funcional
- VerifiedBy: Revisión

## 112: Reservorio He
DeriveReqt
El SOI deberÃ¡ contar con la capacidad de almacenar la masa de helio requerido por el propulsor
- LongName: L1-MIS-014
- ChapterName: L2
- ReqStatus: Asignado
- ReqType: funcional
- VerifiedBy: Revisión

## 113: Interfaz LOX
DeriveReqt
El SOI deberÃ¡ contar con interfases de Oxigeno capaz de vincularse a la base de lanzamiento.
- LongName: L1-MIS-014
- ChapterName: L2
- ReqStatus: Asignado
- ReqType: interface
- VerifiedBy: Revisión

## 114: Interfaz RP1
DeriveReqt
El SOI deberá contar con interfases de Querosén capaz de vincularse a la base de lanzamiento.
- LongName: L1-MIS-014
- ChapterName: L2
- ReqStatus: Asignado
- ReqType: interface
- VerifiedBy: Revisión

## 115: Interfaz N2
DeriveReqt
El SOI deberá contar con interfases de nitrógeno capaz de vincularse a la base de lanzamiento.
- LongName: L1-MIS-014
- ChapterName: L2
- ReqStatus: Asignado
- ReqType: interface
- VerifiedBy: Revisión

## 116: Interfaz He
DeriveReqt
El SOI deberÃ¡ contar con interfases de Helio capaz de vincularse a la base de lanzamiento.
- LongName: L1-MIS-014
- ChapterName: L2
- ReqStatus: Asignado
- ReqType: interface
- VerifiedBy: Revisión

## 117: Interfaz Telemetría
DeriveReqt
El SOI deberá contar con una interfaz física de telemetría a la unidad de control de lanzamiento.
- LongName: L1-MIS-014
- ChapterName: L2
- ReqStatus: Asignado
- ReqType: interface
- VerifiedBy: Revisión

## 118: Interfaz de Comandos
DeriveReqt
El SOI deberá contar con una interfaz física de comandos que lo vincule a la unidad de control de lanzamiento
- LongName: L1-MIS-014
- ChapterName: L2
- ReqStatus: Asignado
- ReqType: interface
- VerifiedBy: Revisión

## 119: Verticalización
DeriveReqt
El SOI deberá contar con un sistema que permita la verticalización del mismo desde la unidad de control de lanzamiento.
- LongName: L1-MIS-014
- ChapterName: L2
- ReqStatus: Asignado
- ReqType: operacional
- VerifiedBy: Revisión

## 120: Operación Autónoma
El Sistema deberá tener la capacidad de operar de manera autónoma una vez dado inicio el lanzamiento, incluyendo la operación de liberación
- ChapterName: L2
- ReqStatus: Asignado
- ReqType: operacional
- VerifiedBy: Revisión
