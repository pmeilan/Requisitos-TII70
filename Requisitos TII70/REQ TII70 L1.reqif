# REQTII70

# Specification: Requirements Document
- ReqIF.Description: Requirements Document

## 4: L0
Cumplimiento de las normativas nacionales e internacionales para la no-proliferación de la Tecnología para Armas de Destrucción Masiva y sus medios de entrega.
- Name: Normas Internacionales
- VerifiedBy: Revisión
- ReqType: restricción
- ReqStatus: aceptado

## 5: L0
Cumplimiento de normativas de aplicación para la protección de la propiedad privada e individuos y los espacios ribereños, marítimos, terrestres y aéreos que sean alcanzados por las actividades.
- Name: Propiedad Privada
- VerifiedBy: Revisión
- ReqType: restricción
- ReqStatus: aceptado

## 3: L0
Los alcances y costo de La misión TII70 deberán ser consistentes con los objetivos estratégicos del programa ISCUL considerando la disponibilidad tecnológica y de infraestructura que garanticen el desarrollo tecnológico y humano.
- Name: Programa
- VerifiedBy: Revisión
- ReqType: restricción
- ReqStatus: aceptado

## 1: L0
El vehiculo TII-70 deberá maximizar el uso de tecnologías aplicables al vehículo TII-250.
- Name: Nivel Tecnológico
- VerifiedBy: Revisión
- ReqType: restricción
- ReqStatus: aceptado

## 2: L0
El vehiculo TII-70 deberá maximizar el uso de conceptos de solución aplicables al vehículo TII-250.
- Name: Alcance Tecnológico
- VerifiedBy: Revisión
- ReqType: restricción
- ReqStatus: aceptado

## 1: L1
La misión TII-70 deberá poder ejecutarse desde el Centro Espacial Punta Indio.
- Name: Centro de Lanzamiento
- VerifiedBy: Revisión
- ReqType: restricción
- ReqStatus: aceptado

## 2: L1
La misión TII-70 deberá tener la capacidad de llevar 100kg como carga útil.
- Name: Capacidad de Carga Útil
- VerifiedBy: Análisis
- ReqType: funcional
- ReqStatus: aceptado

## 5: L1
La misión TII-70 deberá implementar tanques estructurales para propelentes.
- Name: Tanques Estructurales
- VerifiedBy: Revisión
- ReqType: funcional
- ReqStatus: aceptado

## 7: L1
La misión TII-70 deberá utilizar un prototipo de propulsor compatible con el diseño de la segunda etapa del TII-250 adaptado para la misión.
- Name: Propulsor
- VerifiedBy: Revisión
- ReqType: restricción
- ReqStatus: aceptado

## 8: L1
La misión TII-70 deberá tener capacidad de recuperación preservando la integridad estructural del vehículo.
- Name: Recuperación
- VerifiedBy: Revisión
- ReqType: funcional
- ReqStatus: aceptado

## 9: L1
La misión TII-70 seguirá los lineamientos de la “Flight Termination Systems Commonality Standard 319-10” [D.R.11] para vehículos no tripulados.
- Name: Norma 319 FTS
- VerifiedBy: Revisión
- ReqType: restricción
- ReqStatus: aceptado

## 10: L1
La misión TII-70 implementará un plan de vuelo que evite nominalmente el impacto ambiental sobre el área a proteger, adyacente al sitio de lanzamiento, y prevea su disposición final.
- Name: Impacto Ambiental
- VerifiedBy: Análisis
- ReqType: funcional
- ReqStatus: aceptado

## 11: L1
La misión TII-70 deberá cumplir todas las ordenanzas y normativas que apliquen para la preservación del medioambiente y protección de las actividades en la zona.
- Name: Medio Ambiente Local
- VerifiedBy: Revisión
- ReqType: funcional
- ReqStatus: aceptado

## 14: L1
La misión TII-70 deberá lograr superar la linea de Karman durante TBD minutos
- Name: Línea de Karman
- VerifiedBy: Revisión
- ReqType: restricción
- ReqStatus: aceptado

## 15: L1
La misión TII-70 deberá lograr una actitud estabilizada en tres ejes antes del apogeo.
- Name: Control de Actitud
- VerifiedBy: Análisis
- ReqType: funcional
- ReqStatus: aceptado

## 16: L1
La misión TII-70 deberá implementar un simulador funcional del vehiculo y del segmento terreno.
- Name: Simulador de Misión
- VerifiedBy: Inspección
- ReqType: funcional
- ReqStatus: aceptado

## 17: L1
El costo recurrente de cada lanzamiento de Tronador II-70 será menor a u$s 3,3M.
- Name: Costo Recurrente
- VerifiedBy: Análisis
- ReqType: restricción
- ReqStatus: aceptado

## 18: L1
El costo no recurrente del Tronador II-70 será menor a u$s 66M hasta su primer lanzamiento de demostración.
- Name: Costo No Recurrente
- VerifiedBy: Análisis
- ReqType: restricción
- ReqStatus: aceptado

## 19: L1
El primer lanzamiento del TII-70 será en 2026.
- Name: Primer Lanzamiento
- VerifiedBy: Análisis
- ReqType: restricción
- ReqStatus: aceptado

## 20: L1
El cuarto lanzamiento del TII-70 será en 2028.
- Name: Cuarto Lanzamiento
- VerifiedBy: Análisis
- ReqType: restricción
- ReqStatus: aceptado

## 21: L1
La misión TII-70 deberá estimar la confiabilidad para verificar los requisitos de misión con el conjunto de lanzamientos.
- Name: Confiabilidad
- VerifiedBy: Revisión
- ReqType: funcional
- ReqStatus: aceptado

## 22: L1
La misión TII-70 deberá seguir lineamientos de calidad para sistemas espaciales.
- Name: Calidad
- VerifiedBy: Revisión
- ReqType: funcional
- ReqStatus: aceptado

## 25: Objetivo de Misión
Llegar al espacio con vuelos sub orbitales
- ChapterName: L1
- VerifiedBy: Análisis
- ReqType: misión
- ReqStatus: aceptado

## 26: Recuperación de Escombros
La misión TII70 deberá tener la capacidad de recuperar los escombros producidos en caso de percance para evitar el impacto ambiental
- ChapterName: L1
- VerifiedBy: Análisis
- ReqType: operacional
- ReqStatus: aceptado

## 27: Protección al Medio Ambiente
Se deberá dar cumplimiento de las normativas de aplicación para la protección de la propiedad privada e individuos y los espacios ribereños, marítimos, terrestres y aéreos que sean alcanzados por las actividades en el marco del programa ISCUL
- ChapterName: L1
- VerifiedBy: Análisis
- ReqType: restricción
- ReqStatus: aceptado
